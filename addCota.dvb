Attribute VB_Name = "Module1"
Sub addCota()
    Dim ss As AcadSelectionSet
    Dim FilterType(0) As Integer
    Dim FilterData(0) As Variant
    Dim objCota As AcadMText
    Dim dbSoma As Double
    Dim sNum As String
    Dim dbNum As String
    Dim newColor As AcadAcCmColor
    
    Set ss = ThisDrawing.SelectionSets.Add(Now())
    
    Set newColor = New AcadAcCmColor
    newColor.SetRGB 0, 255, 0
    
    FilterType(0) = 0
    FilterData(0) = "MTEXT"
    
    dbSoma = ThisDrawing.Utility.GetReal("Digite o número a ser somado: ")
    ThisDrawing.Utility.Prompt ("Selecione os objetos: ")
    ss.SelectOnScreen FilterType, FilterData
    
    For Each objCota In ss
        sNum = Replace(objCota.TextString, ".", ",")
        
        dbNum = CDbl(sNum) + dbSoma
        sNum = Replace(CStr(dbNum), ",", ".")
        
        objCota.TextString = sNum
        objCota.TrueColor = newColor
        objCota.Update
    Next
    
    
End Sub
